SNIMPY-MIB DEFINITIONS ::= BEGIN

IMPORTS
    MODULE-IDENTITY, OBJECT-TYPE,
    IpAddress, Integer32, Gauge32,
    TimeTicks, Counter64,
    Counter32, mib-2                  FROM SNMPv2-SMI
    DisplayString, TEXTUAL-CONVENTION,
    PhysAddress, TruthValue           FROM SNMPv2-TC
    InetAddressType, InetAddress,
    InetAddressIPv4, InetAddressIPv6  FROM INET-ADDRESS-MIB
    IANAifType                        FROM IANAifType-MIB;


snimpy MODULE-IDENTITY
    LAST-UPDATED "200809160000Z"
    ORGANIZATION
           "snimpy
            https://github.com/vincentbernat/snimpy"
    CONTACT-INFO
           "Lorem ipsum, etc, etc."
    DESCRIPTION
           "This is a test MIB module for snimpy."

    REVISION      "200809160000Z"
    DESCRIPTION   "Last revision"
    ::= { mib-2 45121 }

OddInteger ::= TEXTUAL-CONVENTION
    DISPLAY-HINT "d-2"
    STATUS       current
    DESCRIPTION
	"Testing fmt"
    SYNTAX       INTEGER (6..18 | 20..23 | 27 | 28..1336)

UnicodeString ::= TEXTUAL-CONVENTION
    DISPLAY-HINT "255t"
    STATUS       current
    DESCRIPTION
	"Testing fmt"
    SYNTAX       OCTET STRING (SIZE(0..255))

snimpyScalars OBJECT IDENTIFIER ::= { snimpy 1 }
snimpyTables  OBJECT IDENTIFIER ::= { snimpy 2 }
snimpyTraps   OBJECT IDENTIFIER ::= { snimpy 3 }

snimpyIpAddress OBJECT-TYPE
    SYNTAX 	IpAddress
    MAX-ACCESS  read-only
    STATUS	current
    DESCRIPTION
	"An IP address"
    ::= { snimpyScalars 1 }

snimpyString OBJECT-TYPE
    SYNTAX 	DisplayString (SIZE (0..255))
    MAX-ACCESS  read-only
    STATUS	current
    DESCRIPTION
	"An string to display"
    ::= { snimpyScalars 2 }

snimpyInteger OBJECT-TYPE
    SYNTAX 	OddInteger
    MAX-ACCESS  read-only
    STATUS	current
    DESCRIPTION
	"An integer"
    ::= { snimpyScalars 3 }

snimpyEnum OBJECT-TYPE
    SYNTAX      INTEGER {
                  up(1),
                  down(2),
                  testing(3)
                }
    MAX-ACCESS  read-only
    STATUS	current
    DESCRIPTION
	"An enumeration"
    ::= { snimpyScalars 4 }

snimpyObjectId OBJECT-TYPE
    SYNTAX      OBJECT IDENTIFIER
    MAX-ACCESS  read-only
    STATUS	current
    DESCRIPTION
	"An oid"
    ::= { snimpyScalars 5 }

snimpyBoolean OBJECT-TYPE
    SYNTAX      TruthValue
    MAX-ACCESS  read-only
    STATUS	current
    DESCRIPTION
	"A boolean"
    ::= { snimpyScalars 6 }

snimpyCounter OBJECT-TYPE
    SYNTAX      Counter32
    MAX-ACCESS  read-only
    STATUS	current
    DESCRIPTION
	"A 32 bits counter"
    ::= { snimpyScalars 7 }

snimpyGauge OBJECT-TYPE
    SYNTAX      Gauge32
    MAX-ACCESS  read-only
    STATUS	current
    DESCRIPTION
	"A 32 bits gauge"
    ::= { snimpyScalars 8 }

snimpyTimeticks OBJECT-TYPE
    SYNTAX      TimeTicks
    MAX-ACCESS  read-only
    STATUS	current
    DESCRIPTION
	"A timetick"
    ::= { snimpyScalars 9 }

snimpyCounter64 OBJECT-TYPE
    SYNTAX	Counter64
    MAX-ACCESS  read-only
    STATUS	current
    DESCRIPTION
	"A 64-bit counter"
    ::= { snimpyScalars 10 }

snimpyBits	OBJECT-TYPE
    SYNTAX	BITS {
                  first(0),
		  second(1),
		  third(2),
		  last(7),
		  secondByte(8)
		}
    MAX-ACCESS  read-only
    STATUS	current
    DESCRIPTION
	"A bit field"
    ::= { snimpyScalars 11 }

snimpyNotImplemented OBJECT-TYPE
    SYNTAX 	DisplayString (SIZE (0..255))
    MAX-ACCESS  read-only
    STATUS	current
    DESCRIPTION
	"An string to display (not implemented)"
    ::= { snimpyScalars 12 }

snimpyOctetString OBJECT-TYPE
    SYNTAX 	OCTET STRING
    MAX-ACCESS  read-only
    STATUS	current
    DESCRIPTION
	"An string to display"
    ::= { snimpyScalars 13 }

snimpyUnicodeString OBJECT-TYPE
    SYNTAX 	UnicodeString
    MAX-ACCESS  read-only
    STATUS	current
    DESCRIPTION
	"An unicode string to display"
    ::= { snimpyScalars 14 }

snimpyMacAddress OBJECT-TYPE
    SYNTAX 	PhysAddress
    MAX-ACCESS  read-only
    STATUS	current
    DESCRIPTION
	"A MAC address"
    ::= { snimpyScalars 15 }

snimpyMacAddressInvalid OBJECT-TYPE
    SYNTAX 	DisplayString
    MAX-ACCESS  read-only
    STATUS	current
    DESCRIPTION
	"A MAC address with invalid syntax"
    ::= { snimpyScalars 16 }

-- A simple table

snimpySimpleTable OBJECT-TYPE
    SYNTAX      SEQUENCE OF SnimpySimpleEntry
    MAX-ACCESS  not-accessible
    STATUS      current
    DESCRIPTION
            "A table"
    ::= { snimpyTables 1 }

snimpySimpleEntry OBJECT-TYPE
    SYNTAX      SnimpySimpleEntry
    MAX-ACCESS  not-accessible
    STATUS      current
    DESCRIPTION
            "Entry for our simple table"
    INDEX   { snimpySimpleIndex }
    ::= { snimpySimpleTable 1 }

SnimpySimpleEntry ::=
    SEQUENCE {
        snimpySimpleIndex       Integer32,
        snimpySimpleDescr       DisplayString,
        snimpySimpleType        IANAifType,
        snimpySimplePhys        PhysAddress
    }

snimpySimpleIndex OBJECT-TYPE
    SYNTAX      Integer32 (1..30)
    MAX-ACCESS  not-accessible
    STATUS      current
    DESCRIPTION
            "Index for snimpy simple table"
    ::= { snimpySimpleEntry 1 }

snimpySimpleDescr OBJECT-TYPE
    SYNTAX      DisplayString (SIZE (0..255))
    MAX-ACCESS  read-only
    STATUS      current
    DESCRIPTION
            "Blah blah"
    ::= { snimpySimpleEntry 2 }

snimpySimpleType OBJECT-TYPE
    SYNTAX      IANAifType
    MAX-ACCESS  read-only
    STATUS      current
    DESCRIPTION
            "Blah blah"
    ::= { snimpySimpleEntry 3 }

snimpySimplePhys OBJECT-TYPE
    SYNTAX      PhysAddress
    MAX-ACCESS  read-only
    STATUS      current
    DESCRIPTION
            "Blah blah"
    ::= { snimpySimpleEntry 4 }

-- A more complex table

snimpyComplexTable OBJECT-TYPE
    SYNTAX      SEQUENCE OF SnimpyComplexEntry
    MAX-ACCESS  not-accessible
    STATUS      current
    DESCRIPTION
            "A more complex table"
    ::= { snimpyTables 2 }

snimpyComplexEntry OBJECT-TYPE
    SYNTAX      SnimpyComplexEntry
    MAX-ACCESS  not-accessible
    STATUS      current
    DESCRIPTION
            "Entry for our complex table"
    INDEX   { snimpyComplexFirstIP, snimpyComplexSecondIP }
    ::= { snimpyComplexTable 1 }

SnimpyComplexEntry ::=
    SEQUENCE {
        snimpyComplexFirstIP	 IpAddress,
        snimpyComplexSecondIP    IpAddress,
        snimpyComplexState       INTEGER
    }

snimpyComplexFirstIP OBJECT-TYPE
    SYNTAX      IpAddress
    MAX-ACCESS  not-accessible
    STATUS      current
    DESCRIPTION
            "First IP address for index"
    ::= { snimpyComplexEntry 1 }

snimpyComplexSecondIP OBJECT-TYPE
    SYNTAX      IpAddress
    MAX-ACCESS  not-accessible
    STATUS      current
    DESCRIPTION
            "Second IP address for index"
    ::= { snimpyComplexEntry 2 }

snimpyComplexState OBJECT-TYPE
    SYNTAX      INTEGER {
                  up(1),
                  down(2),
                  testing(3)
		}
    MAX-ACCESS  read-only
    STATUS      current
    DESCRIPTION
	"State for our both IP"
    ::= { snimpyComplexEntry 3 }

-- A table with complex indexes

snimpyIndexTable OBJECT-TYPE
    SYNTAX      SEQUENCE OF SnimpyIndexEntry
    MAX-ACCESS  not-accessible
    STATUS      current
    DESCRIPTION
            "A table with complex indexes"
    ::= { snimpyTables 3 }

snimpyIndexEntry OBJECT-TYPE
    SYNTAX      SnimpyIndexEntry
    MAX-ACCESS  not-accessible
    STATUS      current
    DESCRIPTION
            "Entry for our indexed table"
    INDEX   { snimpyIndexVarLen, snimpyIndexOidVarLen,
    	      snimpyIndexFixedLen, IMPLIED snimpyIndexImplied }
    ::= { snimpyIndexTable 1 }

SnimpyIndexEntry ::=
    SEQUENCE {
        snimpyIndexVarLen	DisplayString,
	snimpyIndexIntIndex	Integer32,
	snimpyIndexOidVarLen	OBJECT IDENTIFIER,
	snimpyIndexFixedLen	DisplayString,
        snimpyIndexImplied      DisplayString,
        snimpyIndexInt          Integer32
    }

snimpyIndexVarLen OBJECT-TYPE
    SYNTAX      DisplayString (SIZE (1..10))
    MAX-ACCESS  read-only
    STATUS      current
    DESCRIPTION
            "Variable length index"
    ::= { snimpyIndexEntry 1 }

snimpyIndexIntIndex OBJECT-TYPE
    SYNTAX      Integer32
    MAX-ACCESS  not-accessible
    STATUS      current
    DESCRIPTION
            "Integer index"
    ::= { snimpyIndexEntry 2 }

snimpyIndexOidVarLen OBJECT-TYPE
    SYNTAX	OBJECT IDENTIFIER
    MAX-ACCESS	not-accessible
    STATUS	current
    DESCRIPTION
	"OID as index"
    ::= { snimpyIndexEntry 3 }

snimpyIndexFixedLen OBJECT-TYPE
    SYNTAX      DisplayString (SIZE (6))
    MAX-ACCESS  not-accessible
    STATUS      current
    DESCRIPTION
            "Fixed length index"
    ::= { snimpyIndexEntry 4 }

snimpyIndexImplied OBJECT-TYPE
    SYNTAX      DisplayString (SIZE (1..30))
    MAX-ACCESS  not-accessible
    STATUS      current
    DESCRIPTION
            "Variable length index, implied"
    ::= { snimpyIndexEntry 5 }

snimpyIndexInt OBJECT-TYPE
    SYNTAX      Integer32
    MAX-ACCESS  read-only
    STATUS      current
    DESCRIPTION
            "An integer of fixed size"
    ::= { snimpyIndexEntry 6 }

-- A table indexed using InetAddresses

snimpyInetAddressTable OBJECT-TYPE
    SYNTAX      SEQUENCE OF SnimpyInetAddressEntry
    MAX-ACCESS  not-accessible
    STATUS      current
    DESCRIPTION
            "A InetAddress table"
    ::= { snimpyTables 4 }

snimpyInetAddressEntry OBJECT-TYPE
    SYNTAX      SnimpyInetAddressEntry
    MAX-ACCESS  not-accessible
    STATUS      current
    DESCRIPTION
            "Entry for our complex table"
    INDEX   { snimpyInetAddressType, snimpyInetAddress }
    ::= { snimpyInetAddressTable 1 }

SnimpyInetAddressEntry ::=
    SEQUENCE {
        snimpyInetAddressType        InetAddressType,
        snimpyInetAddress            InetAddress,
        snimpyInetAddressState       INTEGER
    }

snimpyInetAddressType OBJECT-TYPE
    SYNTAX      InetAddressType
    MAX-ACCESS  not-accessible
    STATUS      current
    DESCRIPTION
            "Address type identifier for snimpyInetAddress"
    ::= { snimpyInetAddressEntry 1 }

snimpyInetAddress OBJECT-TYPE
    SYNTAX      InetAddress
    MAX-ACCESS  not-accessible
    STATUS      current
    DESCRIPTION
            "Type dependent InetAddress"
    ::= { snimpyInetAddressEntry 2 }

snimpyInetAddressState OBJECT-TYPE
    SYNTAX      INTEGER {
                  up(1),
                  down(2),
                  testing(3)
		}
    MAX-ACCESS  read-only
    STATUS      current
    DESCRIPTION
            "State for the IP"
    ::= { snimpyInetAddressEntry 3 }

-- A table that may contain invalid values

snimpyInvalidTable OBJECT-TYPE
    SYNTAX      SEQUENCE OF SnimpyInvalidEntry
    MAX-ACCESS  not-accessible
    STATUS      current
    DESCRIPTION
            "A table"
    ::= { snimpyTables 5 }

snimpyInvalidEntry OBJECT-TYPE
    SYNTAX      SnimpyInvalidEntry
    MAX-ACCESS  not-accessible
    STATUS      current
    DESCRIPTION
            "Entry for our invalid table"
    INDEX   { snimpyInvalidIndex }
    ::= { snimpyInvalidTable 1 }

SnimpyInvalidEntry ::=
    SEQUENCE {
        snimpyInvalidIndex       Integer32,
        snimpyInvalidDescr       DisplayString
    }

snimpyInvalidIndex OBJECT-TYPE
    SYNTAX      Integer32 (1..30)
    MAX-ACCESS  not-accessible
    STATUS      current
    DESCRIPTION
            "Index for snimpy invalid table"
    ::= { snimpyInvalidEntry 1 }

snimpyInvalidDescr OBJECT-TYPE
    SYNTAX      DisplayString (SIZE (0..255))
    MAX-ACCESS  read-only
    STATUS      current
    DESCRIPTION
            "Blah blah"
    ::= { snimpyInvalidEntry 2 }

-- A table that may be empty

snimpyEmptyTable OBJECT-TYPE
    SYNTAX      SEQUENCE OF SnimpyEmptyEntry
    MAX-ACCESS  not-accessible
    STATUS      current
    DESCRIPTION
            "A table"
    ::= { snimpyTables 6 }

snimpyEmptyEntry OBJECT-TYPE
    SYNTAX      SnimpyEmptyEntry
    MAX-ACCESS  not-accessible
    STATUS      current
    DESCRIPTION
            "Entry for our empty table"
    INDEX   { snimpyEmptyIndex }
    ::= { snimpyEmptyTable 1 }

SnimpyEmptyEntry ::=
    SEQUENCE {
        snimpyEmptyIndex       Integer32,
        snimpyEmptyDescr       DisplayString
    }

snimpyEmptyIndex OBJECT-TYPE
    SYNTAX      Integer32 (1..30)
    MAX-ACCESS  not-accessible
    STATUS      current
    DESCRIPTION
            "Index for snimpy empty table"
    ::= { snimpyEmptyEntry 1 }

snimpyEmptyDescr OBJECT-TYPE
    SYNTAX      DisplayString (SIZE (0..255))
    MAX-ACCESS  read-only
    STATUS      current
    DESCRIPTION
            "Blah blah"
    ::= { snimpyEmptyEntry 2 }

-- A table whose index re-uses objects from other tables' indexes

snimpyReuseIndexTable OBJECT-TYPE
    SYNTAX      SEQUENCE OF SnimpyReuseIndexEntry
    MAX-ACCESS  not-accessible
    STATUS      current
    DESCRIPTION
            "A table whose index re-uses objects from
             other tables' indexes"
    ::= { snimpyTables 7 }

snimpyReuseIndexEntry OBJECT-TYPE
    SYNTAX      SnimpyReuseIndexEntry
    MAX-ACCESS  not-accessible
    STATUS      current
    DESCRIPTION
            "Entry for our snimpyReuseIndexTable table
             note that snimpyIndexImplied is not the last item
             so it cannot be implied"
    INDEX   { snimpyIndexImplied, snimpySimpleIndex }
    ::= { snimpyReuseIndexTable 1 }

SnimpyReuseIndexEntry ::=
    SEQUENCE {
        snimpyReuseIndexValue       INTEGER
    }

snimpyReuseIndexValue OBJECT-TYPE
    SYNTAX      INTEGER
    MAX-ACCESS  read-only
    STATUS      current
    DESCRIPTION
            "Integer value"
    ::= { snimpyReuseIndexEntry 1 }

-- A table that augments snimpySimpleTable

snimpyAugmentTable OBJECT-TYPE
    SYNTAX      SEQUENCE OF SnimpyAugmentEntry
    MAX-ACCESS  not-accessible
    STATUS      current
    DESCRIPTION
            "A table that augments snimpySimpleTable"
    ::= { snimpyTables 8 }

snimpyAugmentEntry OBJECT-TYPE
    SYNTAX      SnimpyAugmentEntry
    MAX-ACCESS  not-accessible
    STATUS      current
    DESCRIPTION
            "Entry for our augmenting table"
    AUGMENTS { snimpySimpleEntry }
    ::= { snimpyAugmentTable 1 }

SnimpyAugmentEntry ::=
    SEQUENCE {
        snimpyAugmentExtra       DisplayString
    }

snimpyAugmentExtra OBJECT-TYPE
    SYNTAX      DisplayString (SIZE (0..255))
    MAX-ACCESS  read-only
    STATUS      current
    DESCRIPTION
            "Extra column added by augmentation"
    ::= { snimpyAugmentEntry 1 }

-- A notification

snimpyNotification NOTIFICATION-TYPE
    OBJECTS { snimpySimpleIndex,
              snimpySimpleDescr,
              snimpySimpleType,
              snimpySimplePhys,
              snimpyIpAddress }
    STATUS  current
    DESCRIPTION
            "A notification"
    ::= { snimpyTraps 1 }

END
